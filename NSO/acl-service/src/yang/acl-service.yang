module acl-service {

  namespace "http://example.com/acl-service";
  prefix acl-service;

  import ietf-inet-types {
    prefix inet;
  }
  import tailf-common {
    prefix tailf;
  }
  import tailf-ncs {
    prefix ncs;
  }

  description
    "Bla bla...";

  revision 2016-01-01 {
    description
      "Initial revision.";
  }

  list acccess-list {
    description "This is an RFS skeleton service";


    key name;
    leaf name {
      tailf:info "Unique service id";
      tailf:cli-allow-range;
      type string;
    }

    uses ncs:service-data;
    ncs:servicepoint "acl-service-servicepoint";

    leaf-list device {
      type leafref {
        path "/ncs:devices/ncs:device/ncs:name";
      }
    }
    container default {
        leaf rule {
          type enumeration {
            enum yes;
            enum no;
          }
        }
    }
    
    list rule {
      key name;
      leaf name {
        type string {
          pattern [\S]*;
        }
      }
      leaf description {
        type string;
      }
      leaf action {
        mandatory true;
        type enumeration {
          enum permit;
          enum deny;
        }
      }
      leaf protocol {
        mandatory true;
        type enumeration {
          enum tcp;
          enum udp;
        }
      }
      container source {
        leaf address {
          type union {
            type inet:ip-address;
            type inet:ip-prefix;
          }
          
          mandatory true;
        }
        leaf port {
          type uint16;
        }
      }
      container destination {
        leaf address {
          type union {
            type inet:ip-address;
            type inet:ip-prefix;
          }
          mandatory true;
        }
        leaf port {
          type uint16 {
            range "1..1024";
          }
          mandatory true;
        }
      }
      leaf log {
        type empty;
      }
    }
  }
}
